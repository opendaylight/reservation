/*
 * Copyright (c) 2015 Inocybe Technologies, Inc. and others.  All rights reserved.
 *
 * This program and the accompanying materials are made available under the
 * terms of the Eclipse Public License v1.0 which accompanies this distribution,
 * and is available at http://www.eclipse.org/legal/epl-v10.html
 */
module models-common {
    yang-version 1;

    namespace "urn:opendaylight:reservation-models:models-common";
    prefix "models-common";

    import ietf-inet-types { prefix inet; revision-date "2010-09-24"; }

    description
        "Common bundles types and definitions for reservation models.";

    revision 2015-01-22 {
        description
                "Initial revision.";
    }

    /* "The date-and-time type is a profile of the ISO 8601
     * standard for representation of dates and times using the
     * Gregorian calendar.  The profile is defined by the
     * date-time production in Section 5.6 of RFC 3339.
     *
     *  The date-and-time type is compatible with the dateTime XML
     *  schema type with the following notable exceptions:
     *
     * (a) The date-and-time type does not allow negative years.
     *
     * (b) The date-and-time time-offset -00:00 indicates an unknown
     *     time zone (see RFC 3339) while -00:00 and +00:00 and Z all
     *     represent the same time zone in dateTime.
     *
     *  (c) The canonical format (see below) of data-and-time values
     *      differs from the canonical format used by the dateTime XML
     *      schema type, which requires all times to be in UTC using the
     *      time-offset 'Z'.
     *
     * This type is not equivalent to the DateAndTime textual
     * convention of the SMIv2 since RFC 3339 uses a different
     * separator between full-date and full-time and provides
     * higher resolution of time-secfrac.
     * The canonical format for date-and-time values with a known time
     * zone uses a numeric time zone offset that is calculated using
     * the device's configured known offset to UTC time.  A change of
     * the device's offset to UTC time will cause date-and-time values
     * to change accordingly.  Such changes might happen periodically
     * in case a server follows automatically daylight saving time
     * (DST) time zone offset changes.  The canonical format for
     * date-and-time values with an unknown time zone (usually referring
     * to the notion of local time) uses the time-offset -00:00."
     */
    typedef date-and-time {
        description
                "This type represents object-identifiers restricted to 128 sub-identifiers.
                In the value set and its semantics, this type is equivalent to
                the OBJECT IDENTIFIER type of the SMIv2.";

        reference
                "RFC 2578: Structure of Management Information Version 2 (SMIv2)";
        type string {
            pattern '\d{4}-\d{2}-\d{2}T\d{2}:\d{2}:\d{2}(\.\d+)?'
            + '(Z|[\+\-]\d{2}:\d{2})';
        }
    }

    typedef address {
        type union {
            type phys-address;
            type mac-address;
            type ip-address;
        }
    }

    typedef phys-address {
        type string {
            pattern '([0-9a-fA-F]{2}(:[0-9a-fA-F]{2})*)?';
        }
        description
                "Represents media- or physical-level addresses represented as
                a sequence octets, each octet represented by two hexadecimal numbers.
                Octets are separated by colons. The canonical representation uses
                lowercase characters. In the value set and its semantics, this
                type is equivalent to the PhysAddress textual convention of the
                SMIv2.";
        reference
                "RFC 2579: Textual Conventions for SMIv2";
    }

    typedef mac-address {
        type string {
            pattern '[0-9a-fA-F]{2}(:[0-9a-fA-F]{2}){5}';
        }
        description
                "The mac-address type represents an IEEE 802 MAC address. The
                canonical representation uses lowercase characters. In the value
                set and its semantics, this type is equivalent to the MacAddress
                textual convention of the SMIv2.";
        reference
                "IEEE 802: IEEE Standard for Local and Metropolitan Area Networks:
                Overview and Architecture RFC 2579: Textual Conventions for SMIv2";
    }

    typedef ip-address {
        type union {
            type inet:ipv4-address;
            type inet:ipv6-address;
        }
        description
                "The ip-address type represents an IP address and is IP version
                neutral. The format of the textual representations implies the
                IP version.";
    }

    typedef ipv4-address {
        type string {
            pattern
                        '(([0-9]|[1-9][0-9]|1[0-9][0-9]|2[0-4][0-9]|25[0-5])\.){3}'
            + '([0-9]|[1-9][0-9]|1[0-9][0-9]|2[0-4][0-9]|25[0-5])'
            + '(%[\p{N}\p{L}]+)?';
        }
        description
                "The ipv4-address type represents an IPv4 address in dotted-quad
                notation. The IPv4 address may include a zone index, separated
                by a % sign. The zone index is used to disambiguate identical
                address values. For link-local addresses, the zone index will
                typically be the interface index number or the name of an interface.
                If the zone index is not present, the default zone of the device
                will be used. The canonical format for the zone index is the numerical
                format";
    }

    typedef ipv6-address {
        type string {
            pattern '((:|[0-9a-fA-F]{0,4}):)([0-9a-fA-F]{0,4}:){0,5}'
            + '((([0-9a-fA-F]{0,4}:)?(:|[0-9a-fA-F]{0,4}))|'
            + '(((25[0-5]|2[0-4][0-9]|[01]?[0-9]?[0-9])\.){3}'
            + '(25[0-5]|2[0-4][0-9]|[01]?[0-9]?[0-9])))'
            + '(%[\p{N}\p{L}]+)?';
            pattern '(([^:]+:){6}(([^:]+:[^:]+)|(.*\..*)))|'
            + '((([^:]+:)*[^:]+)?::(([^:]+:)*[^:]+)?)'
            + '(%.+)?';
        }
        description
                "The ipv6-address type represents an IPv6 address in full, mixed,
                shortened, and shortened-mixed notation. The IPv6 address may
                include a zone index, separated by a % sign The zone index is
                used to disambiguate identical address values. For link-local
                addresses, the zone index will typically be the interface index
                number or the name of an interface. If the zone index is not present,
                the default zone of the device will be used. The canonical format
                of IPv6 addresses uses the compressed format described in RFC
                4291, Section 2.2, item 2 with the following additional rules:
                the :: substitution must be applied to the longest sequence of
                all-zero 16-bit chunks in an IPv6 address. If there is a tie,
                the first sequence of all-zero 16-bit chunks is replaced by ::.
                Single all-zero 16-bit chunks are not compressed. The canonical
                format uses lowercase characters and leading zeros are not allowed.
                The canonical format for the zone index is the numerical format
                as described in RFC 4007, Section 11.2.";
        reference
                "RFC 4291: IP Version 6 Addressing Architecture RFC 4007: IPv6
                Scoped Address Architecture RFC 5952: A Recommendation for IPv6
                Address Text Representation";
    }

    typedef ip-prefix {
        type union {
            type inet:ipv4-prefix;
            type inet:ipv6-prefix;
        }
        description
                "The ip-prefix type represents an IP prefix and is IP version
                neutral. The format of the textual representations implies the
                IP version.";
    }
    typedef ipv4-prefix {
        type string {
            pattern
                        '(([0-9]|[1-9][0-9]|1[0-9][0-9]|2[0-4][0-9]|25[0-5])\.){3}'
            + '([0-9]|[1-9][0-9]|1[0-9][0-9]|2[0-4][0-9]|25[0-5])'
            + '/(([0-9])|([1-2][0-9])|(3[0-2]))';
        }
        description
                "The ipv4-prefix type represents an IPv4 address prefix. The prefix
                length is given by the number following the slash character and
                must be less than or equal to 32. A prefix length value of n corresponds
                to an IP address mask that has n contiguous 1-bits from the most
                significant bit (MSB) and all other bits set to 0. The canonical
                format of an IPv4 prefix has all bits of the IPv4 address set
                to zero that are not part of the IPv4 prefix.";
    }

    typedef ipv6-prefix {
        type string {
            pattern
                        '((:|[0-9a-fA-F]{0,4}):)([0-9a-fA-F]{0,4}:){0,5}'
            + '((([0-9a-fA-F]{0,4}:)?(:|[0-9a-fA-F]{0,4}))|'
            + '(((25[0-5]|2[0-4][0-9]|[01]?[0-9]?[0-9])\.){3}'
            + '(25[0-5]|2[0-4][0-9]|[01]?[0-9]?[0-9])))'
            + '(/(([0-9])|([0-9]{2})|(1[0-1][0-9])|(12[0-8])))';
            pattern '(([^:]+:){6}(([^:]+:[^:]+)|(.*\..*)))|'
            + '((([^:]+:)*[^:]+)?::(([^:]+:)*[^:]+)?)'
            + '(/.+)';
        }
        description
                "The ipv6-prefix type represents an IPv6 address prefix. The prefix
                length is given by the number following the slash character and
                must be less than or equal 128. A prefix length value of n corresponds
                to an IP address mask that has n contiguous 1-bits from the most
                significant bit (MSB) and all other bits set to 0. The IPv6 address
                should have all bits that do not belong to the prefix set to zero.
                The canonical format of an IPv6 prefix has all bits of the IPv6
                address set to zero that are not part of the IPv6 prefix. Furthermore,
                IPv6 address is represented in the compressed format described
                in RFC 4291, Section 2.2, item 2 with the following additional
                rules: the :: substitution must be applied to the longest sequence
                of all-zero 16-bit chunks in an IPv6 address. If there is a tie,
                the first sequence of all-zero 16-bit chunks is replaced by ::.
                Single all-zero 16-bit chunks are not compressed. The canonical
                format uses lowercase characters and leading zeros are not allowed.";
        reference
                "RFC 4291: IP Version 6 Addressing Architecture";
    }
}
