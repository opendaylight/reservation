module connection {

  yang-version 1;

  namespace
    "http://www.inocybe.com";

  prefix connection;

  organization "Inocybe";

  contact
    "Mathieu Lemay <mlemay@inocybe.com>,
     Arash Eghtesadi <aeghtesadi@inocybe.com>,
     Gabriel Robitaille-Montpetit <grmontpetit@inocybe.com>,
     Jonathan Fok Kan <jfokkan@inocybe.com>";

  description
    "YANG version of the RESERVATION";

  revision "2014-08-07" {
    description
      "Reservation model in progress.";
  }

  leaf endpointStart {
    type DisplayString;

    description "Where the connection originates.
      Can be a switch port, etc..";
  }

  leaf endpointEnd {
    type int32;
    description "Where the connection originates.
      Can be a switch port, etc..";
  }

  leaf status {
    type enumeration {
      enum "disconnected" {
        value 0;
        description
          "The connection is closed.";
      }
      enum "connecting" {
        value 1;
        description
          "The connection is beign established.";
      }
      enum "established" {
        value 2;
        description
          "The connection is established.";
      }
    }
  }

  leaf type {
    type DisplayString;
  }

  typedef DisplayString {
    type string {
        length "0 .. 255";
    }
    description
     "YANG version of the SMIv2 DisplayString TEXTUAL-CONVENTION.";
    reference
     "RFC 2579, section 2.";
  }

    typedef ipv4-address {
      type string;
    }

    typedef ipv6-address {
      type string;
    }

  container endpoint {

    leaf name {
      type DisplayString;
      config false;
      mandatory true;
      description
        "The name of the endpoint.";
    }

    leaf macAddress {
      type DisplayString;
      config false;
      mandatory false;
      description
        "The MAC address of the endpoint.";
    }

    leaf managementIp {
      type  ipv4-address;
      config false;
      mandatory true;
      description
        "The management ip address of the endpoint.";
    }

    leaf operationIp {
      type  ipv4-address;
      config false;
      mandatory true;
      description
        "The operational ip address of the endpoint.";
    }

    leaf port {
      type DisplayString;
      config false;
      mandatory true;
      description
        "The port number of the endpoint.";
    }

    leaf description {
      type DisplayString;
      config false;
      mandatory false;
      description
        "Adds a description for the endpoint.";
    }
  }
}
