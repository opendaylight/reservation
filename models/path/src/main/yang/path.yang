module path {

  yang-version 1;

  namespace
    "http://www.inocybe.com";

  prefix connection;

  organization "Inocybe";

  contact
    "Mathieu Lemay <mlemay@inocybe.com>,
     Arash Eghtesadi <aeghtesadi@inocybe.com>,
     Gabriel Robitaille-Montpetit <grmontpetit@inocybe.com>,
     Jonathan Fok Kan <jfokkan@inocybe.com>";

  description
    "YANG version of the RESERVATION";

  revision "2014-08-07" {
    description
      "Reservation model in progress.";
  }

  container path {

    leaf-list endpoints {
      type int8;
      description
        "The list of endpoints used by the path.";
    }

    container serviceDefinition {

      leaf service-api {
        type string;
        config false;
        mandatory false;
        description
          "The API to connect to the service.";
      }

      leaf service {
        type string;
        config false;
        mandatory false;
        description
          "The services...";
      }
    }

  }

	container endpoint {

    leaf id {
      type int8;
      config false;
      mandatory true;
      description
        "The unique identifier for the endpoint.";
    }

    leaf name {
      type string;
      config false;
      mandatory true;
      description
        "The name of the endpoint.";
    }

    leaf macAddress {
      type string;
      config false;
      mandatory false;
      description
        "The MAC address of the endpoint.";
    }

    leaf managementIp {
      type string;
      config false;
      mandatory true;
      description
        "The management ip address of the endpoint.";
    }

    leaf operationIp {
      type string;
      config false;
      mandatory true;
      description
        "The operational ip address of the endpoint.";
    }

    leaf port {
      type string;
      config false;
      mandatory true;
      description
        "The port number of the endpoint.";
    }

    leaf bandwitdh {
      type int32;
      config false;
      mandatory true;
      description
        "The bandwidth of the port. This is need by the
         path computation engine.";
    }

    leaf description {
      type string;
      config false;
      mandatory false;
      description
        "Adds a description for the endpoint.";
    }
  }
}
