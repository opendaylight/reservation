/*
 * Copyright (c) 2015 Inocybe Technologies, Inc. and others.  All rights reserved.
 *
 * This program and the accompanying materials are made available under the
 * terms of the Eclipse Public License v1.0 which accompanies this distribution,
 * and is available at http://www.eclipse.org/legal/epl-v10.html
 */

module tl1-southbound-impl {
    yang-version 1;
    namespace "urn:opendaylight:params:xml:ns:yang:tl1:southbound:impl";
    prefix "tl1-southbound-impl";

    import config { prefix config; revision-date 2013-04-05; }
    import opendaylight-md-sal-binding { prefix md-sal-binding; revision-date 2013-10-28; }

    description
        "Service definition for tl1 southbound project";

    revision "2015-06-08" {
        description
                "Initial revision";
    }

    identity tl1-southbound-impl {
        base config:module-type;
        config:java-name-prefix Tl1SouthboundImpl;
    }

    augment "/config:modules/config:module/config:configuration" {
        case tl1-southbound-impl {
            when "/config:modules/config:module/config:type = 'tl1-southbound-impl'";
            container broker {
                uses config:service-ref {
                    refine type {
                        mandatory true;
                        config:required-identity md-sal-binding:binding-broker-osgi-registry;
                    }
                }
            }
        }
    }
}
